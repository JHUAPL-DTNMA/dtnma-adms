module ietf-ari-types {
  yang-version 1.1;
  namespace "ari://ietf/ari-types/";
  prefix ari-types;

  import ietf-amm {
    prefix amm;
  }

  organization
    "Internet Engineering Task Force (IETF)" {
    amm:enum 1;
  }
  contact
    "WG Web: <http://tools.ietf.org/wg/dtn/>
     WG List: <mailto:dtn@ietf.org>

      Editor: Brian Sipos
              <mailto:brian.sipos+ietf@gmail.com>";
  description
    "This module defines native YANG types for the ARI literal
     types that have no single corresponding YANG base type
     (REAL32, REAL64, TP, TD, LABEL, ARITYPE, and OBJPAT),
     for use in ADM modules.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2026-10-19 {
    description
      "Initial revision.";
    reference
      "draft-ietf-dtn-adm-yang";
  }
  amm:enum 27;

  // 32-bit floating point: decimal64 approximation
  typedef real32 {
    amm:enum 8;
    type decimal64 {
      fraction-digits 9;
    }
    description
      "32-bit floating point value (IEEE 754 binary32),
       represented as decimal64 with 9 fractional digits.
       The representable domain is limited to
       -9223372036.854775808 to 9223372036.854775807, and
       the IEEE 754 special values (NaN, Infinity) are
       not representable.";
    reference
      "draft-ietf-dtn-ari";
  }

  // 64-bit floating point: decimal64 approximation
  typedef real64 {
    amm:enum 9;
    type decimal64 {
      fraction-digits 9;
    }
    description
      "64-bit floating point value (IEEE 754 binary64),
       represented as decimal64 with 9 fractional digits.
       The representable domain is limited to
       -9223372036.854775808 to 9223372036.854775807, and
       the IEEE 754 special values (NaN, Infinity) are
       not representable.";
    reference
      "draft-ietf-dtn-ari";
  }

  // DTN Time: seconds since the DTN Epoch, nanosecond precision
  typedef tp {
    amm:enum 12;
    type decimal64 {
      fraction-digits 9;
    }
    units "seconds";
    description
      "DTN Time.
       A time point expressed in seconds as an offset from
       the DTN Epoch 2000-01-01T00:00:00Z, with fractional
       seconds used to represent times down to the
       nanosecond.
       Not affected by leap seconds.";
    reference
      "draft-ietf-dtn-ari";
  }

  // Time delta: seconds with nanosecond precision
  typedef td {
    amm:enum 13;
    type decimal64 {
      fraction-digits 9;
    }
    units "seconds";
    description
      "A time delta (an offset between two time points),
       expressed in seconds, with fractional seconds
       used to represent times down to the nanosecond.
       This is a delta, not an absolute point in time.";
    reference
      "draft-ietf-dtn-ari";
  }

  // A 32-bit signed integer or a restricted text name
  typedef label {
    amm:enum 14;
    type union {
      type int32;
      type string {
        pattern '!?[A-Za-z_][0-9A-Za-z_\-\.]*';
      }
    }
    description
      "A label: a 32-bit signed integer or a restricted text
       name (id-text).";
    reference
      "draft-ietf-dtn-ari";
  }

  // A registered literal type code point or name
  typedef aritype {
    amm:enum 16;
    type union {
      type int32;
      type string {
        pattern '!?[A-Za-z_][0-9A-Za-z_\-\.]*';
      }
    }
    description
      "An ARI literal type identifier: a registered code point
       or a registered type name (id-text).";
    reference
      "draft-ietf-dtn-ari";
  }

  // Four independent path-segment patterns
  typedef objpat {
    type string {
      pattern '^\((\*|(-?[0-9]+\.\.(-?[0-9]+)?|\.\.(-?[0-9]+)?|-?[0-9'
            + ']+)(,(-?[0-9]+\.\.(-?[0-9]+)?|\.\.(-?[0-9]+)?|-?[0-9]+'
            + '))*|!?[A-Za-z_][0-9A-Za-z_\-\.]*)\)\((\*|(-?[0-9]+\.\.'
            + '(-?[0-9]+)?|\.\.(-?[0-9]+)?|-?[0-9]+)(,(-?[0-9]+\.\.(-'
            + '?[0-9]+)?|\.\.(-?[0-9]+)?|-?[0-9]+))*|!?[A-Za-z_][0-9A'
            + '-Za-z_\-\.]*)\)\((\*|(-?[0-9]+\.\.(-?[0-9]+)?|\.\.(-?['
            + '0-9]+)?|-?[0-9]+)(,(-?[0-9]+\.\.(-?[0-9]+)?|\.\.(-?[0-'
            + '9]+)?|-?[0-9]+))*|!?[A-Za-z_][0-9A-Za-z_\-\.]*)\)\((\*'
            + '|(-?[0-9]+\.\.(-?[0-9]+)?|\.\.(-?[0-9]+)?|-?[0-9]+)(,('
            + '-?[0-9]+\.\.(-?[0-9]+)?|\.\.(-?[0-9]+)?|-?[0-9]+))*|!?'
            + '[A-Za-z_][0-9A-Za-z_\-\.]*)\)$';
    }
    description
      "An object reference pattern: four independent path segment
       patterns (organization, model, object type, and object ID),
       each a wildcard, a single value, or a comma-separated set of
       integer intervals.";
    reference
      "draft-ietf-dtn-ari: Object Reference Patterns";
  }
}
