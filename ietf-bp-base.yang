module ietf-bp-base {
  yang-version 1.1;
  namespace "ari://ietf/bp-base/";
  prefix bp-base;

  import ietf-amm {
    prefix amm;
  }
  import ietf-amm-base {
    prefix amm-base;
  }
  import ietf-network-base {
    prefix network-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module implements the DTN Management Architecture (DTNMA)
     Agent core functionality.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2026-04-02 {
    description
      "Updated for latest ADM document.";
    reference
      "draft-ietf-dtn-adm-yang";
  }
  amm:enum 5;

  // Direct encoded Endpoint IDs
  amm:ident display-bstr-eid {
    amm:enum 1;
    description
      "Interpret byte string values as a CBOR-encoded
       BPv7 Endpoint ID value.";
    reference
      "RFC 9171: Bundle Protocol Version 7
       RFC 9758: Updates to the ipn URI scheme";
    amm:base "//ietf/amm-base/IDENT/display-hint-bstr";
  }
  amm:typedef eid-text {
    amm:enum 0;
    description
      "The BP EID in a URI text form.
       Only valid BPv7 schemes SHALL be present in values of
       this type.";
    reference
      "RFC 9171: Bundle Protocol Version 7
       RFC 9758: Updates to the ipn URI scheme";
    amm:type "//ietf/network-base/typedef/uri";
  }
  amm:typedef eid-cbor {
    amm:enum 1;
    description
      "The BP EID in a CBOR binary form.
       This form includes the enclosing array head.";
    reference
      "RFC 9171: Bundle Protocol Version 7
       RFC 9758: Updates to the ipn URI scheme
       draft-ietf-dtn-eid-pattern: Bundle Protocol Endpoint ID
         Patterns";
    amm:type "/aritype/cbor" {
      amm:display-hint "./ident/display-bstr-eid";
    }
  }

  // Encoded Endpoint ID Patterns
  amm:ident display-bstr-eid-pattern {
    amm:enum 3;
    description
      "Interpret byte string values as a CBOR-encoded
       BPv7 Endpoint ID Pattern.";
    reference
      "RFC 9171: Bundle Protocol Version 7
       RFC 9758: Updates to the ipn URI scheme";
    amm:base "//ietf/amm-base/IDENT/display-hint-bstr";
  }
  amm:typedef eid-pattern-cbor {
    amm:enum 2;
    description
      "The BP EID Pattern in a CBOR binary form.
       This form includes the enclosing array head.";
    reference
      "draft-ietf-dtn-eid-pattern: Bundle Protocol Endpoint ID
       Patterns";
    amm:type "/aritype/cbor" {
      amm:display-hint "./ident/display-bstr-eid-pattern";
    }
  }

  // Network endpoints for BP
  amm:ident bp-endpoint {
    amm:enum 0;
    description
      "This object defines parameters for BPv7 transport endpoints.
       The 'eid' uses the binary form for compactness,
       which includes a display-hint to help end users.";
    reference
      "RFC 9171: Bundle Protocol Version 7";
    amm:base "//ietf/network-base/ident/abstract-endpoint";
    amm:parameter eid {
      description
        "The EID of the endpoint.";
      amm:type "./TYPEDEF/eid-cbor";
    }
  }
  amm:oper match-eid-pattern {
    amm:enum 0;
    description
      "This is a unary predicate operator which will compare
       text URI or <./ident/bp-endpoint> reference values against
       an EID pattern.
       The 'pattern' uses the binary form for compactness,
       which includes a display-hint to help end users.";
    reference
      "RFC TBA: Bundle Protocol Endpoint ID Patterns";
    amm:parameter pattern {
      description
        "The EID of the endpoint.";
      amm:type "./TYPEDEF/eid-pattern-cbor";
    }
    amm:operand value {
      description
        "The value to check for a match.";
      amm:union {
        // text URI
        amm:type "//ietf/network-base/typedef/uri";
        // structured EID
        amm:type "/aritype/ident" {
          amm:base "./ident/bp-endpoint";
        }
      }
    }
    amm:result is-match {
      description
        "The result is true if the value matches the given pattern.";
      amm:type "/aritype/bool";
    }
  }
}
